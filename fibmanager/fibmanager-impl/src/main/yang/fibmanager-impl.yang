module fibmanager-impl {
    yang-version 1;
    namespace "urn:opendaylight:params:xml:ns:yang:fibmanager:impl";
    prefix "fibmanager-impl";

    import config { prefix config; revision-date 2013-04-05;}
    import fibmanager-api { prefix fibmgr-api; revision-date 2015-05-08;}
    import opendaylight-md-sal-binding { prefix md-sal-binding; revision-date 2013-10-28;}
    import odl-mdsalutil { prefix odl-mdsal; revision-date 2015-04-10;}
    import vpnmanager-api { prefix odl-vpn; revision-date 2015-05-08;}

    description
        "Service definition for fibmanager project";

    revision "2015-03-25" {
        description
            "Initial revision";
    }

    identity fibmanager-impl {
        base config:module-type;
        config:provided-service fibmgr-api:fibmanager-api;
        config:java-name-prefix FibmanagerImpl;
    }

    augment "/config:modules/config:module/config:configuration" {
        case fibmanager-impl {
            when "/config:modules/config:module/config:type = 'fibmanager-impl'";
            container broker {
                uses config:service-ref {
                    refine type {
                        mandatory true;
                        config:required-identity md-sal-binding:binding-broker-osgi-registry;
                    }
                }
            }
            container mdsalutil {
                uses config:service-ref {
                    refine type {
                        mandatory true;
                        config:required-identity odl-mdsal:odl-mdsalutil;
                    }
                }
            }
            container vpnmanager {
                uses config:service-ref {
                    refine type {
                        mandatory true;
                        config:required-identity odl-vpn:vpnmanager-api;
                    }
                }
            }
        }
    }
}
