module fib-rpc {
    namespace "urn:opendaylight:netvirt:fib:rpc";
    prefix "fib-rpc";

    import opendaylight-flow-types {
        prefix offlow;
        revision-date "2013-10-26";
    }

    revision "2016-01-21" {
        description "FIB Servicer RPC Module";
    }

    /* RPCs */
    grouping fib-entry-inputs {
        leaf source-dpid {
            type uint64;
        }
        leaf vpn-name {
            type string;
        }
        leaf service-id {
            type uint32;
        }
        leaf ip-address {
            type string;
        }
        leaf ip-address-source {
            description
            "This field indicates whether the IP address here is an External-Fixed-Ip(Owned by Router),
            or Floating-Ip(Used by Ports).";
            type enumeration {
              enum "ExternalFixedIP";
              enum "FloatingIP";
            }
        }
    }

    rpc create-fib-entry {
        description "to install FIB/LFIB/TST routes on specified dpn with given instructions";
        input {
            uses fib-entry-inputs;
            uses offlow:instruction-list;
        }
    }

    rpc remove-fib-entry {
        description "to remove FIB/LFIB/TST routes from specified dpn";
        input {
            uses fib-entry-inputs;
        }
    }

    rpc populate-fib-on-dpn {
        description "Populates FIB table in specified DPN";
        input {
            leaf dpid {
                type uint64;
            }
            leaf vpn-id {
                type uint32;
            }
            leaf rd {
                type string;
            }
        }
    }

    rpc cleanup-dpn-for-vpn {
        description "Removes the VPN Fib entries in a given DPN";
        input {
            leaf dpid {
                type uint64;
            }
            leaf vpn-id {
                type uint32;
            }
            leaf rd {
                type string;
            }

        }
    }
}
