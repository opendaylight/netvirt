module odl-fib {
    namespace "urn:opendaylight:vpnservice:fibmanager";
    prefix odl-fib;

    revision "2015-03-30" {
        description "FIB Manager module";
    }

    grouping ipv4Entries{
        list ipv4Entry{
            key  "destPrefix";
            leaf destPrefix {type string;}
            leaf nextHopAddress {type string;}
        }
    }

    grouping vrfEntries{
        list vrfEntry{
            key  "destPrefix";
            leaf destPrefix {
                type string;
                mandatory true;
            }
            leaf label {
                type uint32;
                mandatory true;
            }
            leaf nextHopAddress {
                type string;
            }
        }
    }

    container fibEntries {
        config false;
        list vrfTables{
            key "routeDistinguisher";
            leaf routeDistinguisher {type string;}
            uses vrfEntries;
        }

        container ipv4Table{
            uses  ipv4Entries;
        }
    }
}
