module alivenessmonitor-impl {
    yang-version 1;
    namespace "urn:opendaylight:params:xml:ns:yang:alivenessmonitor:impl";
    prefix "alivenessmonitor-impl";

    import config { prefix config; revision-date 2013-04-05; }
    import opendaylight-md-sal-binding { prefix md-sal-binding; revision-date 2013-10-28;}
    import opendaylight-sal-binding-broker-impl { prefix md-sal-binding-impl; revision-date 2013-10-28;}
    import odl-interface {prefix odlif; revision-date 2015-03-31;}
    //import aliveness-monitor { prefix aliveness-mon; revision-date 2015-06-29; }

    description
        "Service definition for aliveness monitor module";

    revision "2015-07-06" {
        description
            "Initial revision";
    }

    identity alivenessmonitor-impl {
        base config:module-type;
        config:java-name-prefix AlivenessMonitor;
    }

    augment "/config:modules/config:module/config:configuration" {
        case alivenessmonitor-impl {
            when "/config:modules/config:module/config:type = 'alivenessmonitor-impl'";
            container broker {
                uses config:service-ref {
                    refine type {
                        mandatory true;
                        config:required-identity md-sal-binding:binding-broker-osgi-registry;
                    }
                }
            }
            container rpc-registry {
                 uses config:service-ref {
                      refine type {
                         mandatory true;
                         config:required-identity md-sal-binding:binding-rpc-registry;
                      }
                 }
            }
            container notification-publish-service {
                uses config:service-ref {
                    refine type {
                        mandatory true;
                        config:required-identity md-sal-binding-impl:binding-new-notification-publish-service;
                    }
                }
            }
            container notification-service {
                uses config:service-ref {
                    refine type {
                        mandatory true;
                        config:required-identity md-sal-binding-impl:binding-new-notification-service;
                    }
                }
            }
        }
    }
}
