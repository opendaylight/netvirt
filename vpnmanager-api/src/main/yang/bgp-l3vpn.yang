module bgp-l3vpn {
    namespace "urn:opendaylight:l3vpn:bgp";
    prefix bgp-l3vpn;
    
    import l3vpn { prefix l3vpn; revision-date "2014-08-15";}

    revision "2013-09-11" {
        description "L3 VPN Service module";
    }

    grouping bgp-neighbors {
        description
           "The top level container for the list of neighbours of the BGP router.";
        list bgp-neighbor {
            key "ip-address";
            leaf as-number { type uint32; }
            leaf ip-address { type string; mandatory true; }
       }
    }

    grouping bgp-config {
       description
           "The top level container for BGP configuration";
       leaf bgp-ip-address { type string; }
       leaf bgp-router-id { type string; }
       leaf bgp-as { type uint32; mandatory true; } 
    }

    augment "/l3vpn:vpn-instances" {
        container bgp-config { 
            uses bgp-config;
        }
        container bgp-neighbors { 
            uses bgp-neighbors;
        }
    }
}
