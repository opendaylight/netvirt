module elan-statistics {
    namespace "urn:opendaylight:vpnservice:elan:statistics";
    prefix elan-stats;

    import ietf-interfaces {
        prefix if;
    }

    import interface-statistics {
        prefix if-stats;
    }

    revision "2015-08-24" {
        description "YANG model describes rpc to retrieve the different
               ELAN interface statistics ie. packet/byte counts";
    }

    rpc get-elan-interface-statistics {
        input {
            leaf interface-name {
                type leafref {
                    path "/if:interfaces/if:interface/if:name";
                }
            }
        }
        output {
            container stat-result {
                uses if-stats:stat-reply;
            }
        }
    }
}
