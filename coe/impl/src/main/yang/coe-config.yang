module coe-config {
    yang-version 1;
    namespace "urn:opendaylight:netvirt:coe-config";
    prefix "coe-config";

    description
        "Configuration for coe.";

    revision "2018-07-26" {
        description
                "Initial revision.";
    }

    container coe-config {
        config true;
        leaf service-implementation-mode {
            type enumeration {
                enum "kube-proxy";
                enum "odl-kube-proxy";
            }
            default "kube-proxy";
        }
    }
}
