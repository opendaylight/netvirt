module service-meta {
    namespace "urn:opendaylight:netvirt:coe:service-meta";
    prefix "coe-service-meta";

    import ietf-yang-types {
        prefix yang;
        revision-date "2013-07-15";
    }

    revision "2019-01-23" {
        description "Coe Service Meta Information";
    }

    container service-gateway-info {
        description "Contains the list of services to poduuid mapping";

        list service-gateway {
            key gateway-pod-name;
            leaf gateway-pod-name {
                type string;
            }

            leaf gateway-pod-ip-address {
                type string;
                description "ip address of the service gateway";
            }

            leaf gateway-pod-mac-address {
                type string;
                description "MAC address of the associated port.";
            }
        }
    }
}
