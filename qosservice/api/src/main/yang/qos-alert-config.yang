module qosalert-config {
    yang-version 1;
    namespace "urn:opendaylight:netvirt:qosalert:config";
    prefix "qosalert";

    description "This YANG module defines QoS alert configuration.";

    revision "2017-03-01" {
        description "Initial revision of qosalert model";
    }

    container qosalert-config {

    config true;

      leaf qos-alert-enabled {
      description "QoS alert enable-disable config knob";
         type boolean;
         default false;
      }

      leaf qos-drop-packet-threshold {
      description "QoS Packet drop threshold config. Specified as packet drop %";
         type uint8 {
            range "1..100";
         }
         default 5;
      }

      leaf qos-alert-poll-interval {
        description "Polling interval in minutes";
        type uint16 {
            range "1..3600";
        }
        default 2;
      }

    }

}
