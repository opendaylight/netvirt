module l3nexthop {
    namespace "urn:opendaylight:netvirt:l3nexthop";
    prefix l3nexthop;

    revision "2015-04-09" {
        description "L3 NextHop module";
    }

    container l3nexthop {
        config false;
        list vpnNexthops{
            key "vpnId";
            leaf vpnId {type uint32;}
            list vpnNexthop{
                key  "IpAddress MacAddress";
                leaf IpAddress {type string;}
                leaf MacAddress {type string;}
                leaf egressPointer {type uint32;}
                leaf dpnId {type uint64;}
                leaf flowrefCount {type uint16; }
            }
        }
        list tunnelNexthops{
            key "dpnId";
            leaf dpnId {type uint64;}
            list tunnelNexthop{
                key  "IpAddress";
                leaf IpAddress {type string;}
                leaf egressPointer {type uint32;}
            }
        }
    }
}
