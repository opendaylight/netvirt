module fibmanager-api {
    yang-version 1;
    namespace "urn:opendaylight:params:xml:ns:yang:fibmanager:api";
    prefix "fibmanager-api";

    import config { prefix config; revision-date 2013-04-05; }

    description
        "Service definition for fibmanager project";

    revision "2015-05-08" {
        description
            "Initial revision";
    }

    identity fibmanager-api {
        base "config:service-type";
        config:java-class "org.opendaylight.netvirt.fibmanager.api.IFibManager";
    }
}
