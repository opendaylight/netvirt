module netvirt-sfc-acl {
    yang-version 1;
    namespace "urn:opendaylight:netvirt:sfc:acl";
    prefix "acl";

    import ietf-access-control-list { prefix ietf-acl; revision-date 2016-02-18; }
    import yang-ext { prefix ext; }

    revision "2015-01-05" {
        description "Initial revision of netvirt extensions to ietf-acl model";
    }

    augment "/ietf-acl:access-lists/ietf-acl:acl/ietf-acl:access-list-entries/ietf-acl:ace/ietf-acl:matches" {
        description "Match on neutron entities";
        ext:augment-identifier "neutron-matches";
        leaf source-network-uuid {
            description "Match traffic originating on this network";
            type string;
        }
        leaf source-port-uuid {
            description "Match traffic originating on this port";
            type string;
        }
        leaf destination-port-uuid {
            description "Match traffic terminating on this port";
            type string;
        }
    }

    grouping netvirtsfc-acl-actions {
        leaf sfc-name {
            type string;
        }
        leaf sfp-name {
            type string;
        }
        leaf rsp-name {
            type string;
        }
        leaf render-rsp {
            type boolean;
            default "false";
        }
    }

    augment "/ietf-acl:access-lists/ietf-acl:acl/ietf-acl:access-list-entries/ietf-acl:ace/ietf-acl:actions" {
        description "Redirect traffic to SFC identified by either SFC, SFP or RSP";
        ext:augment-identifier "redirect-to-sfc";
        uses netvirtsfc-acl-actions;
    }
}
