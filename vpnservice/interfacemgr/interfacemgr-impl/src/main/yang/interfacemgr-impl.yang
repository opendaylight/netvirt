module interfacemgr-impl {
    yang-version 1;
    namespace "urn:opendaylight:params:xml:ns:yang:interfacemgr:impl";
    prefix "interfacemgr-impl";

    import config { prefix config; revision-date 2013-04-05; }
    import opendaylight-sal-binding-broker-impl { prefix md-sal-binding-impl; revision-date 2013-10-28;}
    import opendaylight-md-sal-binding { prefix md-sal-binding; revision-date 2013-10-28;}
    import odl-interface {prefix odlif; revision-date 2015-03-31;}
    import odl-mdsalutil { prefix odl-mdsal; revision-date 2015-04-10;}

    description
        "Service definition for interfacemgr project";

    revision "2015-03-25" {
        description
            "Initial revision";
    }

    identity interfacemgr-impl {
        base config:module-type;
        config:provided-service odlif:odl-interface;
        config:java-name-prefix InterfacemgrImpl;
    }

    augment "/config:modules/config:module/config:configuration" {
        case interfacemgr-impl {
            when "/config:modules/config:module/config:type = 'interfacemgr-impl'";
            container broker {
                uses config:service-ref {
                    refine type {
                        mandatory true;
                        config:required-identity md-sal-binding:binding-broker-osgi-registry;
                    }
                }
            }
            container mdsalutil {
                uses config:service-ref {
                    refine type {
                        mandatory true;
                        config:required-identity odl-mdsal:odl-mdsalutil;
                    }
                }
            }
            container rpc-registry {
                uses config:service-ref {
                    refine type {
                        mandatory true;
                        config:required-identity md-sal-binding:binding-rpc-registry;
                    }
                }
            }
            container notification-service {
                 uses config:service-ref {
                     refine type {
                         mandatory true;
                         config:required-identity md-sal-binding-impl:binding-new-notification-service;
                     }
                 }
            }
        }
    }
}
