module vpnmanager-api {
    yang-version 1;
    namespace "urn:opendaylight:params:xml:ns:yang:vpnmanager:api";
    prefix "vpnmanager-api";

    import config { prefix config; revision-date 2013-04-05; }

    description
        "Service definition for vpnmanager project";

    revision "2015-05-08" {
        description
            "Initial revision";
    }

    identity vpnmanager-api {
        base "config:service-type";
        config:java-class "org.opendaylight.netvirt.vpnmanager.api.IVpnManager";
        config:disable-osgi-service-registration;
        status deprecated;
    }
}
