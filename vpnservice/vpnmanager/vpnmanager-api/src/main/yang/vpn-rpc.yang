module vpn-rpc {
    namespace "urn:opendaylight:netvirt:vpn:rpc";
    prefix "vpn-rpc";

    revision "2016-02-01" {
        description "VPN Service RPC Module";
    }

    /* RPCs */
    rpc add-static-route {
        description "Creates a static route in a VPN, creating a new label if needed";
        input {
            leaf vpnInstanceName {
                mandatory true;
                type string;
            }
            leaf destination {
                mandatory true;
                type string;
            }
            leaf nexthop {
                description "Ip-address of the nexthop. The RPC will check if this nexthop is the endpoint
                             of a VPN in an InterVpnLink";
                mandatory true;
                type string;
            }
            leaf label {
                description "Label for the static route. It can be left empty, in that case a new
                            label will be autogenerated";
                type uint32;
            }
        }
        output {
            leaf label {
                description "The auto-generated label, if applies";
                type uint32;
            }
        }
    }

    rpc remove-static-route {
        description "Removes a static route in a VPN, identified by this vpn name, destination and nexthop.
                     Nextop is optional. If specified, the RPC will just remove one of the nexthops in the
                     route (ECMP feature). If not specified, the whole route will be removed";
        input {
            leaf vpnInstanceName {
                mandatory true;
                type string;
            }
            leaf destination {
                mandatory true;
                type string;
            }
            leaf nexthop {
                description "Ip-address of the nexthop. If specified, just one nexthop will be removed. Removing
                             the last nexthop in a route, will provoke the removal of the whole route";
                type string;
            }
        }
    }

    rpc generate-vpn-label {
        description "to generate label for the given ip prefix from the associated VPN";
        input {
            leaf vpn-name {
                type string;
            }
            leaf ip-prefix {
                type string;
            }
        }
        output {
            leaf label {
                type uint32;
            }
        }
    }

    rpc remove-vpn-label {
        description "to remove label for the given ip prefix from the associated VPN";
        input {
            leaf vpn-name {
                type string;
            }
            leaf ip-prefix {
                type string;
            }
        }
    }

    rpc get-existing-operational-vpn {
        description "Checks if another VPN with the same RD is already operational";
        input {
            leaf rd {
                type string;
            }
        }
        output {
            leaf vpn-name {
                type string;
            }
        }
    }
}
