module vpnservice-impl {
    yang-version 1;
    namespace "urn:opendaylight:params:xml:ns:yang:vpnservice:impl";
    prefix "vpnservice-impl";

    import config { prefix config; revision-date 2013-04-05; }
    import opendaylight-md-sal-binding { prefix md-sal-binding; revision-date 2013-10-28;}
    import opendaylight-sal-binding-broker-impl { prefix md-sal-binding-impl; revision-date 2013-10-28;}
    import vpnmanager-api { prefix vpnmgr-api; revision-date 2015-05-08;}
    import odl-mdsalutil { prefix odl-mdsal; revision-date 2016-04-06;}

    description
        "Service definition for vpnservice project";

    revision "2015-02-16" {
        description
            "Initial revision";
    }

    identity vpnservice-impl {
        base config:module-type;
        config:provided-service vpnmgr-api:vpnmanager-api;
        config:java-name-prefix VpnserviceImpl;
    }

    augment "/config:modules/config:module/config:configuration" {
        case vpnservice-impl {
            when "/config:modules/config:module/config:type = 'vpnservice-impl'";
            container broker {
                uses config:service-ref {
                    refine type {
                        mandatory true;
                        config:required-identity md-sal-binding:binding-broker-osgi-registry;
                    }
                }
            }
            container rpcregistry {
                uses config:service-ref {
                    refine type {
                        mandatory true;
                        config:required-identity md-sal-binding:binding-rpc-registry;
                    }
                }
            }
            container mdsalutil {
                uses config:service-ref {
                    refine type {
                        mandatory true;
                        config:required-identity odl-mdsal:odl-mdsalutil;
                    }
                }
            }
            container notification-service {
                uses config:service-ref {
                    refine type {
                        mandatory true;
                        config:required-identity md-sal-binding-impl:binding-new-notification-service;
                    }
                }
            }
            container notification-publish-service {
                uses config:service-ref {
                    refine type {
                        mandatory true;
                        config:required-identity md-sal-binding-impl:binding-new-notification-publish-service;
                    }
                }
            }
        }
    }
}
