module cloud-service-chain-state {
    namespace "urn:opendaylight:netvirt:cloud-servicechain:state";
    prefix "cloud-service-chain-state";

    import yang-ext {prefix ext; revision-date "2013-07-09";}
    import elan {prefix elan; revision-date "2015-06-02";}

    description
        "Holds all cloud-servicechain state data";

    revision "2017-05-11" {
        description
            "Initial revision";
    }

    container vpn-to-pseudo-port-list {
        description "Makes a correspondence between VPNs and stateful information regarding
                     their corresponding VpnPseudoPort";
        list vpn-to-pseudo-port-data {
            key vrf-id;
            leaf vrf-id {
                description "VPN's route distinguisher";
                type string;
            }
            leaf vpn-lport-tag {
                description "Vpn Pseudo Logical Port Tag. There is only one VpnPseudoPort per VPN";
                type uint32;
            }
            leaf scf-tag {
                description "SCF tag associated to Vlan Pseudo Logical Port Tag";
                type uint16;
            }
            leaf scf-table-id {
                description "OF-Table Id in the SCF Pipeline to send packets to, depending on wether
                             the VpnPseudoPort has been used in Uplink or Downlink direction.
                             There is a restriction that states that a VpnPseudoPort can only
                             act as ingress port either in Uplink or in Downlink, but not both";
                type uint8;
            }
        }
    }

    grouping elan-to-pseudo-port-data-list {
        list elan-to-pseudo-port-data {
            key "elan-lport-tag scf-tag";
            description "Relates elan-logical-port and scfTag";
            max-elements "unbounded";
            min-elements "0";

            leaf elan-lport-tag {
                description "Elan Pseudo Logical Port Tag";
                type uint32;
            }

            leaf scf-tag {
                description "SCF tag associated to Elan Pseudo Logical Port Tag";
                type uint32;
            }
        }
    }

    augment "/elan:elan-instances/elan:elan-instance" {
        ext:augment-identifier "elan-service-chain-state";
        uses elan-to-pseudo-port-data-list;
    }
}
