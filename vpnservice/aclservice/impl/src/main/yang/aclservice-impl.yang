module aclservice-impl {
    yang-version 1;
    namespace "urn:opendaylight:netvirt:aclservice:impl";
    prefix "aclservice-impl";

    import config {prefix config; revision-date 2013-04-05;}
    import opendaylight-md-sal-binding { prefix md-sal-binding; revision-date 2013-10-28;}
    import odl-mdsalutil { prefix odl-mdsal; revision-date 2016-04-06;}
    import aclservice-api { prefix sg-api; revision-date 2016-06-08;}

    description
        "Service definition for ACL service project";

    revision "2016-05-23" {
        description
            "Initial revision";
    }

    identity aclservice-impl {
        base config:module-type;
        config:provided-service sg-api:aclservice-api;
        config:java-name-prefix AclServiceImpl;
    }

    augment "/config:modules/config:module/config:configuration" {
        case aclservice-impl {
            when "/config:modules/config:module/config:type = 'aclservice-impl'";
            container broker {
                uses config:service-ref {
                    refine type {
                        mandatory true;
                        config:required-identity md-sal-binding:binding-broker-osgi-registry;
                    }
                }
            }
            container rpc-registry {
                uses config:service-ref {
                     refine type {
                        mandatory true;
                        config:required-identity md-sal-binding:binding-rpc-registry;
                     }
                }
            }
            container mdsalutil {
                uses config:service-ref {
                    refine type {
                        mandatory true;
                        config:required-identity odl-mdsal:odl-mdsalutil;
                    }
                }
            }

        }
    }
}
