module natservice-impl {
    yang-version 1;
    namespace "urn:opendaylight:params:xml:ns:yang:natservice:impl";
    prefix "natservice-impl";

    import config { prefix config; revision-date 2013-04-05; }
    import opendaylight-md-sal-binding { prefix md-sal-binding; revision-date 2013-10-28;}
    import opendaylight-sal-binding-broker-impl { prefix md-sal-binding-impl; revision-date 2013-10-28; }
    import odl-mdsalutil { prefix odl-mdsal; revision-date 2016-04-06;}
    import odl-interface {prefix odlif; revision-date 2016-04-06;}

    description
        "Service definition for NAT Service module";

    revision "2016-01-11" {
        description
            "Initial revision";
    }

    identity natservice-impl {
        base config:module-type;
        config:java-name-prefix NATService;
    }

    augment "/config:modules/config:module/config:configuration" {
        case natservice-impl {
            when "/config:modules/config:module/config:type = 'natservice-impl'";
            container broker {
                uses config:service-ref {
                    refine type {
                        mandatory true;
                        config:required-identity md-sal-binding:binding-broker-osgi-registry;
                    }
                }
            }
            container rpc-registry {
                 uses config:service-ref {
                      refine type {
                         mandatory true;
                         config:required-identity md-sal-binding:binding-rpc-registry;
                      }
                 }
            }
            container notification-service {
                uses config:service-ref {
                    refine type {
                        mandatory true;
                        config:required-identity md-sal-binding-impl:binding-new-notification-service;
                    }
                }
            }
            container mdsalutil {
                uses config:service-ref {
                    refine type {
                        mandatory true;
                        config:required-identity odl-mdsal:odl-mdsalutil;
                    }
                }
            }
            container odlinterface {
                uses config:service-ref {
                    refine type {
                        mandatory true;
                        config:required-identity odlif:odl-interface;
                    }
                }
            }
        }
    }
}
