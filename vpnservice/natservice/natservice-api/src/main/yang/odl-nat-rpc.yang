module odl-nat-rpc {
    namespace "urn:opendaylight:netvirt:natservice:rpc";
    prefix odl-nat-rpc;

    import ietf-yang-types { prefix "yang"; }
    import ietf-inet-types {
        prefix inet;
        revision-date "2013-07-15";
    }

    revision "2017-02-09" {
        description "NAT RPC module";
    }

    grouping nat-router-info {
        leaf router-uuid {
            description "Router UUID";
            type yang:uuid;
        }
        leaf router-name {
            description "Router Name";
            type string;
        }
    }

    grouping snat-state {
        list snat-ip-mapping {
            leaf internal-ip {
                description "Internal IP Address of VM";
                type string;
            }
            leaf internal-port {
                description "Internal Port";
                type string;
            }
            leaf external-ip {
                description "External Fixed IP Address used for SNAT Translation";
                type string;
            }
            leaf external-port {
                description "External Port used for SNAT Translation";
                type string;
            }
            leaf protocol {
                description "Protocol Type";
                type string;
            }
        }
    }

    grouping dnat-configuration {
        list dnat-ip-mapping {
            leaf internal-ip {
                description "Internal IP Address";
                type string;
            }
            leaf external-ip {
                description "Floating IP Address used for DNAT Translation";
                type string;
            }
        }
    }

    grouping nat-output {
        list router-nat {
            key router-uuid;
            uses nat-router-info;
            uses dnat-configuration;
            uses snat-state;
        }
    }

    rpc get_nat_translations_on_router {
        description "Provides the NAT translations for given router uuid";
        input {
            leaf router-uuid {
                description "Router UUID";
                mandatory true;
                type yang:uuid;
            }
        }
        output {
            uses nat-output;
        }
    }
    /*
    Sample output of get_nat_translations_on_router RPC
    {
    "output": {
      "router-nat": [
        {
          "router-uuid": "feca5b1a-8ca8-43c1-b85d-80542144435d",
          "snat-ip-mapping": [
            {
              "external-port": "49152",
              "internal-port": "33811",
              "internal-ip": "20.0.0.5",
              "external-ip": "172.170.0.3",
              "protocol": "TCP"
            }
          ],
          "router-name": "router2",
          "dnat-ip-mapping": [
            {
              "external-ip": "172.170.0.100",
              "internal-ip": "20.0.0.5"
            }
          ]
        }
      ]
    }
  }
  */


    rpc get_nat_translations_on_vpn {
        description "Provides the NAT translations for given vpn uuid";
        input {
            leaf vpn-uuid {
                description "External VPN UUID";
                mandatory true;
                type yang:uuid;
            }
        }
        output {
            uses nat-output;
        }
    }
    /*
    Sample output for get_nat_translations_on_vpn RPC
    {
    "output": {
      "router-nat": [
        {
          "router-uuid": "2e4563c4-c051-44f9-a84a-0d6814f2b83e",
          "router-name": "router1",
          "snat-ip-mapping": [
            {
              "external-port": "49152",
              "internal-port": "39268",
              "internal-ip": "10.0.0.5",
              "external-ip": "172.160.0.3",
              "protocol": "TCP"
            }
          ]
        },
        {
          "router-uuid": "feca5b1a-8ca8-43c1-b85d-80542144435d",
          "snat-ip-mapping": [
            {
              "external-port": "49152",
              "internal-port": "33811",
              "internal-ip": "20.0.0.5",
              "external-ip": "172.170.0.3",
              "protocol": "TCP"
            }
          ],
          "router-name": "router2",
          "dnat-ip-mapping": [
            {
              "external-ip": "172.170.0.100",
              "internal-ip": "20.0.0.5"
            }
          ]
        }
      ]
    }
    */


    rpc get_nat_translations_for_network_and_ipaddress {
        description "Provides the NAT translations for given IP Address";
        input {
            leaf network-uuid {
                description "Network UUID of the Internal IP address provided";
                mandatory true;
                type yang:uuid;
            }
            leaf ip-address {
                description "Internal IP address of VM";
                mandatory true;
                type inet:ip-address;
            }
        }
        output {
            leaf external-ip-address {
                description "External IP address used for NAT translation";
                type string;
            }
            leaf nat-translation {
                description "Represents whether its an SNAT or DNAT translation";
                type string;
            }
        }
    }
    /*
    {
    "output": {
      "nat-translation": "DNAT",
      "external-ip-address": "172.160.0.100"
    }
    }
    */
}
