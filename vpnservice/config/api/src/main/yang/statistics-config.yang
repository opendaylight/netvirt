module statistics-config {
    yang-version 1;
    namespace "urn:opendaylight:netvirt:config:statistics";
    prefix "statistics-config";

    description
        "Configuration for statistics bundle";

    revision "2017-03-26" {
        description
                "Initial revision";
    }

    grouping statistics-config {
        leaf node-counter-result-timeout {
            description "Timout for all ports statistics - in seconds";
            type uint16;
            default 5;
        }
    }
}
