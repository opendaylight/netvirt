module dhcpservice-impl {
    yang-version 1;
    namespace "urn:opendaylight:params:xml:ns:yang:dhcpservice:impl";
    prefix "dhcpservice-impl";

    import config { prefix config; revision-date 2013-04-05; }
    import opendaylight-md-sal-binding { prefix md-sal-binding; revision-date 2013-10-28;}
    import odl-mdsalutil { prefix odl-mdsal; revision-date 2016-04-06;}
    //import neutronvpn-api { prefix nvpn; revision-date 2015-08-12;}
    import opendaylight-entity-ownership-service { prefix eos; revision-date 2015-08-10;}
    import odl-interface {prefix odlif; revision-date 2016-04-06;}

    description
        "Service definition for dhcpservice project";

    revision "2015-07-10" {
        description
            "Initial revision";
    }

    identity dhcpservice-impl {
        base config:module-type;
        config:java-name-prefix DhcpServiceImpl;
    }

    augment "/config:modules/config:module/config:configuration" {
        case dhcpservice-impl {
            when "/config:modules/config:module/config:type = 'dhcpservice-impl'";
            container broker {
                uses config:service-ref {
                    refine type {
                        mandatory true;
                        config:required-identity md-sal-binding:binding-broker-osgi-registry;
                    }
                }
            }
            container rpcregistry {
                uses config:service-ref {
                    refine type {
                        mandatory true;
                        config:required-identity md-sal-binding:binding-rpc-registry;
                    }
                }
            }
            container notification-service {
                uses config:service-ref {
                    refine type {
                        mandatory true;
                        config:required-identity md-sal-binding:binding-notification-service;
                    }
                }
            }

            container mdsalutil {
                uses config:service-ref {
                    refine type {
                        mandatory true;
                        config:required-identity odl-mdsal:odl-mdsalutil;
                    }
                }
            }

            /*container neutronvpn {
                uses config:service-ref {
                    refine type {
                        mandatory true;
                        config:required-identity nvpn:neutronvpn-api;
                    }
                }
            }*/

            container entity-ownership-service {
                uses config:service-ref {
                    refine type {
                        mandatory true;
                        config:required-identity eos:entity-ownership-service;
                    }
                }
            }

            container odlinterface {
                uses config:service-ref {
                    refine type {
                        mandatory true;
                        config:required-identity odlif:odl-interface;
                    }
                }
            }

            leaf controller-dhcp-enabled {
                description "Enable the dhcpservice on the controller";
                type boolean;
            }
        }
    }
}
