module dhcp_allocation_pool {
    namespace "urn:opendaylight:netvirt:dhcp_allocation_pool";
    prefix "dhcp_allocation_pool";

    import ietf-inet-types {
        prefix inet;
        revision-date "2013-07-15";
    }

    import ietf-yang-types {
        prefix yang;
    }

    revision "2016-12-14" {
        description "It provides required datastore containers to handle DHCP requests
            coming from access or external tunnel ports";
    }

    container dhcp_allocation_pool {
        config true;
        description "contains non-neutron DHCP allocation";
        list network {
            key "network-id";
            leaf network-id {
                description "network (elan-instance) id";
                type string;
            }

            list allocations {
                key "subnet";
                leaf subnet {
                    description "subnet for the dhcp to allocate ip addresses";
                    type inet:ip-prefix;
                }

                list allocation-instance {
                    key "mac";
                    leaf mac {
                        description "requesting mac";
                        type yang:phys-address;
                    }
                    leaf allocated-ip {
                        description "allocated ip address";
                        type inet:ip-address;
                    }
                }
            }

            list allocation-pool {
                key "subnet";
                leaf subnet {
                    description "subnet for the dhcp to allocate ip addresses";
                    type inet:ip-prefix;
                }
                leaf allocate-from {
                    description "low allocation limit";
                    type inet:ip-address;
                }
                leaf allocate-to {
                    description "high allocation limit";
                    type inet:ip-address;
                }
                leaf gateway {
                    description "default gateway for dhcp allocation";
                    type inet:ip-address;
                }
                leaf-list dns-servers {
                    description "dns server list";
                    type inet:ip-address;
                }
                list static-routes {
                    description "static routes list for dhcp allocation";
                    key "destination";
                    leaf destination {
                        description "destination in CIDR format";
                        type inet:ip-prefix;
                    }
                    leaf nexthop {
                        description "router ip address";
                        type inet:ip-address;
                    }
                }
            }
        }
    }
}
