module dhcpservice-api {
    yang-version 1;
    namespace "urn:opendaylight:params:xml:ns:yang:dhcpservice:api";
    prefix "dhcpservice-api";

    revision "2015-07-10" {
        description
            "Initial revision for DHCP Service module";
    }

    container interface-name-mac-addresses {
        config false;
        description
            "Container to hold list of interface names and MAC address";

        list interface-name-mac-address {
            max-elements "unbounded";
            min-elements "0";
            key "interface-name";
            description
                "Specifies the name of the interface";

            leaf interface-name {
                type string;
                description
                    "The name of the interface.";
            }

            leaf mac-address {
                type string;
                description
                    "The VM mac address for the interface.";
            }
        }
    }

    container subnet-dhcp-port-data {
        config true;
        description
            "Container to hold DHCP Neutron Port information allocated for the Subnet";
        list subnet-to-dhcp-port {
            key "subnet-id";
            leaf subnet-id { type string;}
            leaf port-name { type string;}
            leaf port-fixedip { type string;}
            leaf port-macaddress { type string;}
        }
    }
}
