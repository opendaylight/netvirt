module federation-plugin-routed-rpc {
    yang-version 1;
    namespace "urn:opendaylight:netvirt:federation:plugin:routed:rpc";
    prefix "federation-plugin-routed-rpc";

    import yang-ext {
        prefix ext;
        revision-date "2013-07-09";
    }

    import ietf-yang-types {
        prefix yang;
    }

    import federation-plugin-manager {
        prefix federation-plugin-manager;
    }

    revision "2017-02-19" {
        description "Federation plugin model";
    }

    rpc update-federated-networks {
        input {
            leaf route-key-item {
                type instance-identifier;
                ext:context-reference federation-plugin-manager:mgr-context;
            }

            list federated-networks-in {
                key self-net-id;
                uses federation-plugin-manager:federated-nets;
            }

            list federated-acls-in {
                key self-acl-id;
                uses federation-plugin-manager:federated-acls-mapping;
            }
        }
    }
}
