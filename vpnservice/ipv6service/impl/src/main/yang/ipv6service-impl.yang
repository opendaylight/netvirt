module ipv6service-impl {
    yang-version 1;
    namespace "urn:opendaylight:netvirt:ipv6service:impl";
    prefix "ipv6service-impl";

    import config { prefix config; revision-date 2013-04-05; }
    import odl-interface {prefix odlif; revision-date 2016-04-06;}
    import odl-mdsalutil { prefix odl-mdsal; revision-date 2016-04-06;}
    import opendaylight-md-sal-binding { prefix md-sal-binding; revision-date 2013-10-28;}
    import opendaylight-md-sal-dom {prefix dom; revision-date 2013-10-28;}

    description
        "Service definition for ipv6service project";

    revision "2016-06-20" {
        description
            "Initial revision";
    }

    identity ipv6service-impl {
        base config:module-type;
        config:java-name-prefix Ipv6ServiceImpl;
    }

    augment "/config:modules/config:module/config:configuration" {
        case ipv6service-impl {
            when "/config:modules/config:module/config:type = 'ipv6service-impl'";
            container broker {
                uses config:service-ref {
                    refine type {
                        mandatory true;
                        config:required-identity md-sal-binding:binding-broker-osgi-registry;
                    }
                }
            }
            container schema-service {
                uses config:service-ref {
                    refine type {
                        mandatory false;
                        config:required-identity dom:schema-service;
                    }
                }
            }
            container notification-service {
               uses config:service-ref {
                  refine type {
                    mandatory true;
                    config:required-identity md-sal-binding:binding-notification-service;
                  }
               }
            }
            container data-broker {
                uses config:service-ref {
                  refine type {
                    mandatory false;
                    config:required-identity md-sal-binding:binding-async-data-broker;
                  }
                }
            }
            container rpcregistry {
                uses config:service-ref {
                  refine type {
                    mandatory true;
                    config:required-identity md-sal-binding:binding-rpc-registry;
                  }
                }
            }
            container mdsalutil {
                uses config:service-ref {
                    refine type {
                        mandatory true;
                        config:required-identity odl-mdsal:odl-mdsalutil;
                    }
                }
            }
            container odlinterface {
                uses config:service-ref {
                    refine type {
                        mandatory true;
                        config:required-identity odlif:odl-interface;
                    }
                }
            }
        }
    }
}
