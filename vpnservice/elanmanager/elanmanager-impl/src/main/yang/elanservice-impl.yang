module elanservice-impl {
    yang-version 1;
    namespace "urn:opendaylight:params:xml:ns:yang:elanservice:impl";
    prefix "elanservice-impl";

    import config { prefix config; revision-date 2013-04-05; }
    import opendaylight-md-sal-binding { prefix md-sal-binding; revision-date 2013-10-28;}
    import opendaylight-sal-binding-broker-impl { prefix md-sal-binding-impl; revision-date 2013-10-28;}
    import opendaylight-entity-ownership-service { prefix eos; revision-date 2015-08-10;}
    import elanmanager-api { prefix elanmgr-api; revision-date 2015-07-07;}
    import odl-mdsalutil { prefix odl-mdsal; revision-date 2016-04-06;}
    import odl-interface {prefix odlif; revision-date 2016-04-06;}
    import itm {prefix itm; revision-date 2016-04-06;}

    description
        "Service definition for elanservice project";

    revision "2015-02-16" {
        description
            "Initial revision";
    }

    identity elanservice-impl {
        base config:module-type;
        config:provided-service elanmgr-api:elanmanager-api;
        config:java-name-prefix elanServiceImpl;
    }

    augment "/config:modules/config:module/config:configuration" {
        case elanservice-impl {
            when "/config:modules/config:module/config:type = 'elanservice-impl'";
            container broker {
                uses config:service-ref {
                    refine type {
                        mandatory true;
                        config:required-identity md-sal-binding:binding-broker-osgi-registry;
                    }
                }
            }
            container rpcregistry {
                uses config:service-ref {
                    refine type {
                        mandatory true;
                        config:required-identity md-sal-binding:binding-rpc-registry;
                    }
                }
            }
            container mdsalutil {
                uses config:service-ref {
                    refine type {
                        mandatory true;
                        config:required-identity odl-mdsal:odl-mdsalutil;
                    }
                }
            }
            container odlinterface {
                uses config:service-ref {
                    refine type {
                        mandatory true;
                        config:required-identity odlif:odl-interface;
                    }
                }
            }
            container itmmanager {
                uses config:service-ref {
                    refine type {
                        mandatory true;
                        config:required-identity itm:itm;
                    }
                }
            }
            container notification-service {
                uses config:service-ref {
                    refine type {
                        mandatory true;
                        config:required-identity md-sal-binding-impl:binding-new-notification-service;
                    }
                }
            }
            container entity-ownership-service {
                uses config:service-ref {
                    refine type {
                        mandatory true;
                        config:required-identity eos:entity-ownership-service;
                    }
                }
            }
            leaf int-bridge-gen-mac {
                type boolean;
            }
        }
    }
}
