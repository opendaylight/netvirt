module elan-config {
    yang-version 1;
    namespace "urn:opendaylight:netvirt:elan:config";
    prefix "elan-config";

    description
        "Configuration for elanmanager";

    revision "2015-07-10" {
        description
                "Initial revision";
    }

    container elan-config {
        config true;
        leaf auto-create-bridge {
            description "If true, auto-create default bridge";
            type boolean;
            default true;
        }
        leaf int-bridge-gen-mac {
            description "If true, generate a mac, else use the bridge generated mac";
            type boolean;
            default true;
        }
        leaf controller-max-backoff {
            description "max_backoff in milliseconds for controller configured
                on OVS Bridge. A null value means use switch default";
            type uint32 {
                range "1000..max";
            }
        }
        leaf controller-inactivity-probe {
            description "inactivity_probe timeout in milliseconds for
                controller configured on OVS Bridge.
                null - Use switch default
                0    - Disable inactivity probes";
            type uint32;
        }
        leaf temp-smac-learn-timeout {
            description "Temporary source MAC learning timeout";
            type uint16;
            default 10;
        }
        leaf punt-lldp-to-controller {
            description "Determines whether LLDP are punt to controller or dropped";
            type boolean;
            default false;
        }
        leaf auto-config-transport-zones {
            description "Determines whether transport zones should be automatically created/updated";
            type boolean;
            default true;
        }
        leaf use-of-tunnels {
            type boolean;
            default false;
        }
        leaf openstack-vni-semantics-enforced {
            type boolean;
            default true;
        }
        leaf l2gw-stale-vlan-cleanup-delay-secs {
            description "Stale vlan bindings cleanup delay after the southbound node is connected";
            type uint16;
            default 900;
        }
        leaf l2gw-logical-switch-delay-secs {
            description "The delay after which logical switch is deleted post l2gw connection deleted";
            type uint16;
            default 20;
        }
    }
}
