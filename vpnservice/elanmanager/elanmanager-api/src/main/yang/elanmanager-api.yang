module elanmanager-api {
    yang-version 1;
    namespace "urn:opendaylight:params:xml:ns:yang:elanmanager:api";
    prefix "elanmanager-api";

    import config { prefix config; revision-date 2013-04-05; }

    description
        "Service definition for elanmanager project";

    revision "2015-07-07" {
        description
            "Initial revision";
    }

    identity elanmanager-api {
        base "config:service-type";
        config:java-class "org.opendaylight.netvirt.elanmanager.api.IElanService";
        config:disable-osgi-service-registration;
        status deprecated;
    }
}
