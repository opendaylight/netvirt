module etree {
    namespace "urn:opendaylight:netvirt:elan:etree";
    prefix elan-etree;

    import elan {prefix elan;}

    import yang-ext {prefix ext; revision-date "2013-07-09";}

    import hwvtep {prefix hwvtep;}

    import network-topology {prefix "topo"; revision-date "2013-10-21"; }

    revision "2016-06-14" {
        description "etree module";
    }

    typedef etree-leaf-tag {
        type    uint32;
        description "Unique identifier across all the tenants for the ETREE's leafs.
                         Each ETree instance has 2 unique tags: elan-tag for roots and etree-leaf-tag for leafs.";
    }

    augment "/elan:elan-interfaces/elan:elan-interface" {
        ext:augment-identifier "etree-interface";
        leaf etree-interface-type {
            type enumeration {
                enum leaf;
                enum root;
            }
            description "Etree's type of the interface - Leaf or Root.";
        }
    }

    augment "/elan:elan-instances/elan:elan-instance" {
        ext:augment-identifier "etree-instance";
        leaf etree-leaf-tag-val {
            type    etree-leaf-tag;
        }
    }

    augment "/elan:elan-tag-name-map/elan:elan-tag-name" {
        ext:augment-identifier "etree-leaf-tag-name";
        leaf etree-leaf-tag {
            type    etree-leaf-tag;
        }
    }
    
    container etree-logical-switches {
        description "logical switch entity in a L2GW device which belongs to the etree network";
        list etree-logical-switch  {
            key "name";
            max-elements "unbounded";
            min-elements "0";
            leaf name {
                type leafref {
                    path "/hwvtep:hwvtep-global-attributes/hwvtep:logical-switches/hwvtep:hwvtep-node-name";
                }
            }
            leaf switch-interfaces-type {
                type enumeration {
                    enum leaf;
                    enum root;
                }
                description "The type of the etree interfaces behind the logical switch. Leaves or Roots.";
            }
        }
    }
}
