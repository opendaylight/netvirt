module l3nexthop {
    namespace "urn:opendaylight:vpnservice:l3nexthop";
    prefix l3nexthop;

    revision "2015-04-09" {
        description "L3 NextHop module";
    }

    container l3nexthop {
        config false;
        list vpnNexthops{
            key "vpnId";
            leaf vpnId {type uint32;}
            list vpnNexthop{
                key  "IpAddress";
                leaf IpAddress {type string;}
                leaf egressPointer {type uint32;}
            }
        }
        list tunnelNexthops{
            key "dpnId";
            leaf dpnId {type uint64;}
            list tunnelNexthop{
                key  "IpAddress";
                leaf IpAddress {type string;}
                leaf egressPointer {type uint32;}
            }
        }
    }

    rpc getEgressPointer {
        description "returns egress pointer, an OF Group Id";
        input {
            leaf dpnId {type uint64;}
            leaf vpnId { type uint32;}  /* optional */
            leaf ipPrefix {type string;}
            leaf nexthopIp {type string;}
        }
        output {
            leaf egressPointer {type uint32;}
            leaf localDestination {type boolean;}
        }
    }

    rpc removeLocalNextHop {
        description "remove a local next hop";
        input {
            leaf dpnId {type uint64;}
            leaf vpnId { type uint32;}  /* optional */
            leaf ipPrefix {type string;}
            leaf nexthopIp {type string;}
        }
    }
}
