module vpn-config {
    yang-version 1;
    namespace "urn:opendaylight:netvirt:vpn:config";
    prefix "vpn-config";

    description
        "Configuration for vpnmanager";

    revision "2016-11-30" {
        description
                "Initial revision";
    }

    container vpn-config {
        config true;
        leaf migrate-ip-cache-size {
            description "Migrate IP cache size";
            type uint64;
            default 10000;
        }
        leaf ip-learn-timeout {
            description "IP learning timeout value (unit - ms)";
            type uint32;
            default 2000;
        }
        leaf boot-delay-arp-learning {
            description "Boot delay (in seconds) to be enforced for arp learning";
            type uint32;
            default 300;
        }
        leaf subnet-route-punt-timeout {
            description "hard timeout value for learnt flows for subnet route punts (unit - seconds).
                To turn off the rate limiting and installation of learnt flows, it should be set to 0";
            type uint32;
            default 10;
        }
        leaf ipv6-nd-monitor-failure-threshold {
            description "IPv6 ND monitor failure threshold";
            type uint32;
            default 2;
        }
        leaf ipv6-nd-monitor-interval {
            description "IPv6 ND monitor interval (unit - secs)";
            type uint32;
            default 120;
        }
        leaf ipv6-nd-monitor-window {
            description "IPv6 ND monitor window";
            type uint32;
            default 4;
        }
    }
}
