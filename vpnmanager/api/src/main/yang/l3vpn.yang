module l3vpn {
  namespace "urn:huawei:params:xml:ns:yang:l3vpn";
// replace with IANA namespace when assigned
  prefix "l3vpn";

  import bgp {
    prefix bgp;
    //draft-zhdankin-netmod-bgp-cfg
  }
  import ietf-interfaces {
    prefix if;
    //rfc7223-YANG Interface Management
  }

  import ietf-inet-types {
    prefix inet;
    revision-date "2013-07-15";
    //RFC6991
  }

  import ietf-yang-types {
    prefix yang;
    //RFC6991
  }

  import neutronvpn {
    prefix nvpn;
    revision-date "2015-06-02";
  }

  description
    "This YANG module defines the generic configuration data for L3VPN service.

     Terms and Acronyms

     BGP (bgp): Border Gateway Protocol
     IPv4 (ipv4):Internet Protocol Version 4
     IPv6 (ipv6): Internet Protocol Version 6

    ";

  revision 2014-08-15 {
    description
      "Initial revision.";
      reference "RFC4271, RFC4364, RFC4760";
  }

  grouping augment-bgp-af-vpn-config {
    description
      "A set of configuration parameters that is applicable to both BGP-VPNv4
      and BGP-VPNv6 address family.";

    leaf apply-label-per-nexthop {
      description
        "The apply-label per-nexthop command enables the ASBR to allocate
         labels for IPv4 VPN routes or IPv6 VPN routes based on the next hop.";



      config "true";
      type boolean;
      default "false";
    }

    leaf upeEnable {
      description
        "Specify peer as UPE.";

      config "true";
      type boolean;
      default "false";
    }

  }


  grouping bgp-af-vpn-instance-config {

    container router-id {
      description
        "The router-id command configures router ID for BGP VPN instance IPv4
        or IPv6 address family.
        By default, no router ID is configured for BGP VPN instance IPv4 or
        IPv6 address family, and the BGP router ID is used as the router ID.";

      leaf enable {
        type boolean;
      }

      choice config-type {
        case static {
          leaf ip-address {
            description
              "Specifies the router ID of a BGP VPN instance IPv4 address
               family. The router ID is expressed in the IPv4 address format.
               ";

            config "true";
            type inet:ip-address;
          }
        }
        case auto-select {
          leaf enable-auto-select {
            description
              "Configures automatic route ID selection for the current BGP VPN
               instance address family.";


            config "true";
            type boolean;
          }
        }
      }
    }

    leaf auto-frr {
      description
        "The auto-frr command enables BGP Auto FRR.";

      config "true";
      type boolean;
      default "false";
    }

    container bgpPeers {
      list bgpPeer {
      key "peerAddr";
      max-elements "unbounded";
      min-elements "0";
        description
          "BGP Peer configure class";

        leaf peerAddr {
          description
            "The nerighbor address";
            config "true";
            type inet:ip-address;
            mandatory true;
        }

          leaf groupName {
            description "peerGroupName";
            config "true";
            type string {
              length "1..47";
            }
          }
          leaf remoteAs {
            description "Specifies the AS number of the peer.";
            config "true";
            type string {
              length "1..11";
            }
          }

          leaf description {

            description
              "specifies the description. The description is a string of letters
               or figures. The value ranges from 1 to 80 characters without
               spaces.";
          config "true";
            type string {
              length "1..80";
              pattern "([^?]*)";
            }
          }

          leaf soo {
            description
              "The peer soo command configures the Site of Origin (SoO)
               attribute for an EBGP peer in a BGP VPN instance. Format is ASN:nn
               or IP-address:nn.";

          config "true";
          type string {
            length "3..21";
          }
        }

        leaf substituteAsEnable {
          description
            "Using the peer substitute-as command, you can substitute the AS
             number of the specified peer in the as-path with the local AS
             number.";

          config "true";
          type boolean;
            default "false";
        }

      }
    }

  }



  /*
   * Binding Interfaces to a VPN Instance.
   */

  container vpn-interfaces {
    description
      "VPN is enabled on interfaces.";

    list vpn-interface  {
      key "name";
      max-elements "unbounded";
      min-elements "0";
      leaf name {
        type leafref {
          path "/if:interfaces/if:interface/if:name";
        }
      }
      list vpn-instance-names {
        key "vpn-name";
        leaf vpn-name {
            type string {
                length "1..40";
            }
        }
        leaf associated-subnet-type {
          type enumeration {
             enum V4Subnet {
                value "0";
                description "V4 Router Internal VPN";
             }
             enum V6Subnet {
                value "1";
                description "V6 Router Internal VPN";
             }
             enum V6InternetVPN {
                value "2";
                description "BGPVPN Internet";
             }
             enum V4AndV6Subnets {
                value "3";
                description "BGPVPN dual stack or V6/V4 Router or undefined";
             }
          }
        }
      }
      leaf dpn-id {
        type uint64;
      }
      leaf router-interface {
          type boolean;
      }
      uses nvpn:network-attributes;
    }
  }

  container vrfInfo {
    description
      "Display the information of the vrf.


      It is intended that this container may be augmented by vendors to
      reflect the vendor-specific operational state parameters.";

    leaf vrfCreateTime {
      description
        "CreateTime of the vrf.";
      config "false";
      type yang:timestamp;
    }

    leaf vrfUpTime {
      description
        "UpTime period of the vrf.";
      config "false";
      type yang:timeticks;
    }

    leaf label {
      description
        "Label of the vrf.";
      config "false";
      type uint32 {
        range "16..1048574";
      }
    }

    leaf vrfStatus {
      description
        "vrf status.";
      config "false";
      type enumeration {
        enum up {
          value "0";
          description "vrf up.";
        }
        enum down {
          value "1";
          description "vrf down.";
        }
      }
    }
  }


  /*
   * augment some bgp vpn functions in bgp module.
   */
  augment "/bgp:bgp-router/bgp:vpnv4/bgp:unicast" {

    uses augment-bgp-af-vpn-config;

  }

  augment "/bgp:bgp-router/bgp:vpnv6/bgp:unicast" {
    uses augment-bgp-af-vpn-config;

  }

  augment "/bgp:bgp-router" {

    container bgp-af-ipv4-vpn-instances {
      description
        "vpn-instances ipv4 address family.";
      list bgp-af-ipv4-vpn-instance {
        key "vpn-instance-name";
        max-elements "unbounded";
        min-elements "0";
        leaf vpn-instance-name {
          type string;
        }
        uses bgp-af-vpn-instance-config;
      }
    }

    container bgp-af-ipv6-vpn-instances {
      description
        "vpn-instances ipv6 address family.";
      list bgp-af-ipv6-vpn-instance {
        key "vpn-instance-name";
        max-elements "unbounded";
        min-elements "0";
        leaf vpn-instance-name {
          type string;
        }
        uses bgp-af-vpn-instance-config;
      }
    }

  }


}
