module neutronvpn-impl {
    yang-version 1;
    namespace "urn:opendaylight:params:xml:ns:yang:neutronvpn:impl";
    prefix "neutronvpn-impl";

    import config { prefix config; revision-date 2013-04-05; }
    import neutronvpn-api { prefix neutronvpn-api; revision-date 2015-08-12;}
    import opendaylight-md-sal-binding { prefix md-sal-binding; revision-date 2013-10-28;}
    import opendaylight-sal-binding-broker-impl { prefix md-sal-binding-impl; revision-date 2013-10-28;}
    import odl-mdsalutil { prefix odl-mdsal; revision-date 2015-04-10;}
    import opendaylight-entity-ownership-service { prefix eos; revision-date 2015-08-10;}

    description
        "Service definition for neutronvpn project";

    revision "2015-03-25" {
        description
            "Initial revision";
    }

    identity neutronvpn-impl {
        base config:module-type;
        config:provided-service neutronvpn-api:neutronvpn-api;
        config:java-name-prefix NeutronvpnImpl;
    }

    augment "/config:modules/config:module/config:configuration" {
        case neutronvpn-impl {
            when "/config:modules/config:module/config:type = 'neutronvpn-impl'";
            container broker {
                uses config:service-ref {
                    refine type {
                        mandatory true;
                        config:required-identity md-sal-binding:binding-broker-osgi-registry;
                    }
                }
            }
            container rpc-registry {
                 uses config:service-ref {
                      refine type {
                         mandatory true;
                         config:required-identity md-sal-binding:binding-rpc-registry;
                      }
                 }
            }
            container mdsalutil {
                uses config:service-ref {
                    refine type {
                        mandatory true;
                        config:required-identity odl-mdsal:odl-mdsalutil;
                    }
                }
            }
            container entity-ownership-service {
                uses config:service-ref {
                    refine type {
                        mandatory true;
                        config:required-identity eos:entity-ownership-service;
                    }
                }
            }

            container binding-normalized-node-serializer {
                uses config:service-ref {
                    refine type {
                        mandatory true;
                        config:required-identity md-sal-binding:binding-normalized-node-serializer;
                    }
                }
            }

            container notification-publish-service {
                uses config:service-ref {
                    refine type {
                         mandatory true;
                         config:required-identity md-sal-binding-impl:binding-new-notification-publish-service;
                    }
                }
            }
            container notification-service {
                uses config:service-ref {
                    refine type {
                         mandatory true;
                         config:required-identity md-sal-binding-impl:binding-new-notification-service;
                         }
                }
            }
        }
    }
}
