module neutronvpn-api {
    yang-version 1;
    namespace "urn:opendaylight:params:xml:ns:yang:neutronvpn:api";
    prefix "neutronvpn-api";

    import config { prefix config; revision-date 2013-04-05; }

    description
        "Service definition for neutronvpn project";

    revision "2015-08-12" {
        description
            "Initial revision";
    }

    identity neutronvpn-api {
        base "config:service-type";
        config:java-class "org.opendaylight.vpnservice.neutronvpn.interfaces.INeutronVpnManager";
    }
}
