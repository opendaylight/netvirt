module odl-mdsalutil {
	yang-version 1;
    namespace "urn:opendaylight:params:xml:ns:yang:mdsalutil:api";
    prefix "odl-mdsal";

    import config { prefix config; revision-date 2013-04-05; }
 
    description
        "Service definition for MD-SAL Util.";
 
    revision "2015-04-10" {
        description
            "Initial revision";
    }

    identity odl-mdsalutil {
        base "config:service-type";
        config:java-class "org.opendaylight.vpnservice.mdsalutil.interfaces.IMdsalApiManager";
    }
}
