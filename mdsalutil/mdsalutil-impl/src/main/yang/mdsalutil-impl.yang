module mdsalutil-impl {
    yang-version 1;
    namespace "urn:opendaylight:params:xml:ns:yang:mdsalutil:impl";
    prefix "mdsalutil-impl";

    import config { prefix config; revision-date 2013-04-05; }
    import opendaylight-md-sal-binding { prefix md-sal-binding; revision-date 2013-10-28;}
    import odl-mdsalutil { prefix odl-mdsal; revision-date 2015-04-10;}

    description
        "Service definition for mdsal project";

    revision "2015-04-03" {
        description
            "Initial revision";
    }

    identity mdsalutil-impl {
       base config:module-type;
       config:provided-service odl-mdsal:odl-mdsalutil;
       config:java-name-prefix Mdsaluttilimpl;
    }

    augment "/config:modules/config:module/config:configuration" {
        case mdsalutil-impl {
            when "/config:modules/config:module/config:type = 'mdsalutil-impl'";
            container broker {
                uses config:service-ref {
                    refine type {
                        mandatory true;
                        config:required-identity md-sal-binding:binding-broker-osgi-registry;
                    }
                }
            }  
               
        }
    }
}
