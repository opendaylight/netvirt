module itm-state {

      namespace "urn:opendaylight:vpnservice:itm:op";

      prefix itm-state;

      import ietf-interfaces {
          prefix if;
      }

      import ietf-yang-types {
          prefix yang;
      }

      import ietf-inet-types {
          prefix inet;
          revision-date "2010-09-24";
      }
      import odl-interface {
          prefix odlif; revision-date "2015-03-31";
      }
    

      description "This YANG module defines operation part of the model.";

      revision "2015-07-01";

        /* Operational state */

      container dpn-endpoints {

        list DPN-TEPs-info {

          key "DPN-ID";

          leaf DPN-ID {
                   type uint64;
          }
          leaf up {
             type boolean;
             config false;
          }

          /* Minimum 1 port. We may for now support only two ports */
          list tunnel-end-points {

               key "portname VLAN-ID ip-address"; /* Multiple tunnels on the same physical port but on different VLAN can be supported */

                 leaf portname {
                     type string;
                     }
                 leaf VLAN-ID {
                     type uint16;
                     }
                 leaf ip-address {
                     type inet:ip-address;
                 }
                 leaf subnet-mask {
                     type inet:ip-prefix;
                 }
                 leaf gw-ip-address {
                          type inet:ip-address;
                 }
                 leaf transport-zone {
                          type string;
                 }
                 leaf interface-name {
                          type string;
                 }
                 leaf tunnel-type {
                      type identityref {
                          base odlif:tunnel-type-base;
                      }
                 }
           }

         }
      }


      container tunnel-list {
             list internal-tunnel {

               key  "source-DPN destination-DPN";

               leaf source-DPN {
                   type uint64;
               }

               leaf destination-DPN {
                   type uint64;
               }

               /* logical-group interface id */

               leaf tunnel-interface-name {
                    type string;
               }
             }
          }

      container external-tunnel-list {
             list external-tunnel {

               key  "source-device destination-device";

               leaf source-device {
                   type string; //dpnid or node-id
               }

               leaf destination-device {
                   type string; //dpn-id or node-id or ip
               }

               /* logical-group interface id */

               leaf tunnel-interface-name {
                    type string;
               }

             }
          }


          notification itm-tunnel-build-complete{
          }

}
