module vpnservice-impl {
    yang-version 1;
    namespace "urn:opendaylight:params:xml:ns:yang:vpnservice:impl";
    prefix "vpnservice-impl";

    import config { prefix config; revision-date 2013-04-05; }
    import opendaylight-md-sal-binding { prefix md-sal-binding; revision-date 2013-10-28;}

    description
        "Service definition for vpnservice project";

    revision "2015-02-16" {
        description
            "Initial revision";
    }

    identity vpnservice-impl {
        base config:module-type;
        config:java-name-prefix VpnserviceImpl;
    }

    augment "/config:modules/config:module/config:configuration" {
        case vpnservice-impl {
            when "/config:modules/config:module/config:type = 'vpnservice-impl'";
            container broker {
                uses config:service-ref {
                    refine type {
                        mandatory true;
                        config:required-identity md-sal-binding:binding-broker-osgi-registry;
                    }
                }
            }
        }
    }
}
