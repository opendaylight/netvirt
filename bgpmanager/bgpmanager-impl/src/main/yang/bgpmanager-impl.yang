module bgpmanager-impl {
    yang-version 1;
    namespace "urn:opendaylight:params:xml:ns:yang:bgpmanager:impl";
    prefix "bgpmanager-impl";

    import config { prefix config; revision-date 2013-04-05; }
    import opendaylight-md-sal-binding { prefix md-sal-binding; revision-date 2013-10-28;}
    import bgpmanager-api { prefix bgpmgr-api; revision-date 2015-04-20;}
    //import itm { prefix itm; revision-date 2015-07-01; }

    description
        "Service definition for bgpmanager project";

    revision "2015-03-26" {
        description
            "Initial revision";
    }

    identity bgpmanager-impl {
        base config:module-type;
        config:provided-service bgpmgr-api:bgpmanager-api;
        config:java-name-prefix BgpManagerImpl;
    }

    augment "/config:modules/config:module/config:configuration" {
        case bgpmanager-impl {
            when "/config:modules/config:module/config:type = 'bgpmanager-impl'";
            container broker {
                uses config:service-ref {
                    refine type {
                        mandatory true;     //true or false
                        config:required-identity md-sal-binding:binding-broker-osgi-registry;
                    }
                }
            }
            /*container itm {
                uses config:service-ref {
                    refine type {
                        mandatory true;
                        config:required-identity itm:itm;
                    }
                }
            }*/
        }
    }
}
