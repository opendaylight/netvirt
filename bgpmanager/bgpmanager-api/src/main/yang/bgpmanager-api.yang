module bgpmanager-api {
	yang-version 1;
    namespace "urn:opendaylight:params:xml:ns:yang:bgpmanager:api";
    prefix "bgpmgr-api";

    import config { prefix config; revision-date 2013-04-05; }

    description
        "Service definition for bgpmanager project";

    revision "2015-04-20" {
        description
            "Initial revision";
    }

    identity bgpmanager-api {
        base "config:service-type";
        config:java-class "org.opendaylight.bgpmanager.api.IBgpManager";
    }
}
